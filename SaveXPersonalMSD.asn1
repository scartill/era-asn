-- Описание минимального набора данных службы
-- спутниковой "кнопки жизни" для персонального терминала
SaveXPersonalMSD

DEFINITIONS AUTOMATIC TAGS ::= BEGIN

IMPORTS VehicleLocation FROM SaveXCommon
        VehicleLocationDelta FROM SaveXCommon
        AdditionalData FROM SaveXCommon;

-- Сообщение
SaveXPersonalMSD ::= SEQUENCE {
    msd SaveXPersonalStructure,
    optionalAdditionalData AdditionalData OPTIONAL,
    ...
}

-- Типы событий
PersonalTrigger ::= ENUMERATED {
    -- Нажатие кнопки
    manual (1),

    -- Внешнее устройство
    external (2),

    -- Геозонирование
    geofencing (3),

    -- Датчики жизненных показателей
    vitals (4),
    ...
}

-- Минимальный набор данных
SaveXPersonalStructure ::= SEQUENCE {
    -- Метка времени
    timestamp INTEGER (0.. 4294967295),

    -- Идентификатор пользователя (UUID)
    uuidA PrintableString (SIZE (8)) (FROM ("a" .. "h" | "0" .. "9")),
    uuidB PrintableString (SIZE (4)) (FROM ("a" .. "h" | "0" .. "9")),
    uuidC PrintableString (SIZE (4)) (FROM ("a" .. "h" | "0" .. "9")),
    uuidD PrintableString (SIZE (4)) (FROM ("a" .. "h" | "0" .. "9")),
    uuidE PrintableString (SIZE (12)) (FROM ("a" .. "h" | "0" .. "9")),

    -- Тип события
    trigger PersonalTrigger,

    -- Текущее местонахождение
    deviceLocation VehicleLocation
}

END.
