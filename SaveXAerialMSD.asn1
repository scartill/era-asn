-- Описание минимального набора данных службы
-- спутниковой "кнопки жизни" для терминала для
-- воздушных судов
SaveXAerialMSD

DEFINITIONS AUTOMATIC TAGS ::= BEGIN

IMPORTS VehicleLocation FROM SaveXCommon
        VehicleLocationDelta FROM SaveXCommon
        AdditionalData FROM SaveXCommon
        CraftDirection FROM SaveXCommon;

-- Сообщение
SaveXAerialMSD ::= SEQUENCE {
    msd SaveXAerialStructure,
    optionalAdditionalData AdditionalData OPTIONAL,
    ...
}

SaveXAerialStructure ::= SEQUENCE {
    -- Метка времени
    timestamp INTEGER (0.. 4294967295),

    -- Серийный номер в соотвествии с ANSI/CTA-2063-A
    icaoMfrCode PrintableString (SIZE (4)) (FROM ("A" .. "H" | "J" .. "N" | "P" .. "Z" | "0" .. "9")),
    lenthCode PrintableString (SIZE (4)) (FROM ("A" .. "F" | "1" .. "9")),
    serial PrintableString (SIZE (15)) (FROM ("A" .. "H" | "J" .. "N" | "P" .. "Z" | "0" .. "9" | " ")),

    -- Текущее местонахождение
    aircraftLocation VehicleLocation,

    -- Курс  
    aircraftDirection CraftDirection,

    -- Предыдущие местоположения
    recentAircraftLocationN1 VehicleLocationDelta OPTIONAL,
    recentAircraftLocationN2 VehicleLocationDelta OPTIONAL,

    -- Идентификатор воздушного судна (24-битный идентификатор ИКАО)
    icaoID OCTET STRING OPTIONAL
}

END.
